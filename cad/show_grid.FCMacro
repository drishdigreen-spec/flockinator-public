import FreeCAD as App, FreeCADGui as Gui
doc=App.openDocument('Flockinator-grid-fit.FCStd')
for o in doc.Objects:
    o.ViewObject.Visibility=True
    if o.TypeId=='Mesh::Feature':
        o.ViewObject.ShapeColor=(0.92,0.92,0.85) if o.Name.startswith('Skin_') else (0.22,0.23,0.25)
    elif o.Name.startswith('Node_'):
        o.ViewObject.ShapeColor=(0.08,0.12,0.16)
    elif o.Name.startswith('Span_'):
        o.ViewObject.ShapeColor=(1.0,0.45,0.08)
    elif o.Name.startswith('HiddenVolume_'):
        o.ViewObject.ShapeColor=(0.2,0.65,0.95);o.ViewObject.Transparency=75;o.ViewObject.Visibility=False
doc.Backing.ViewObject.ShapeColor=(0.3,0.3,0.32)
Gui.updateGui()
Gui.activeDocument().activeView().viewTop();Gui.activeDocument().activeView().fitAll()
Gui.updateGui()
Gui.activeDocument().activeView().saveImage('grid-top.png',1600,1600,'White')
Gui.activeDocument().activeView().viewAxonometric();Gui.updateGui();Gui.activeDocument().activeView().fitAll()
import re
v=Gui.activeDocument().activeView()
camera=v.getCamera()
camera=re.sub(r'nearDistance\s+[-+0-9.eE]+','nearDistance 0.1',camera)
camera=re.sub(r'farDistance\s+[-+0-9.eE]+','farDistance 100000',camera)
v.setCamera(camera)
Gui.updateGui()
Gui.activeDocument().activeView().saveImage('grid-isometric.png',1600,1200,'White')
Gui.activeDocument().activeView().viewTop();Gui.updateGui();Gui.activeDocument().activeView().fitAll()
doc.recompute();doc.save()
